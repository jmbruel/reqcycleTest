# Specification: Specification Document
- Description: Requirements Document

## R1
La MI doit etre sécurisée

## R3
La MI doit pouvoir se défendre des cambrioleurs

## R2
La MI y doit être sécurisée contre le piratage

## R4
La MI doit être équipée d'au moins un détecteur de fumée

## R5
La MI doit contacter la police en cas d'intrusion

## R6
La MI ne doit proposer l'accés qu'à certains utilisateurs
